CAMEL-datatypes {}

DEFINITIONS IMPLICIT TAGS ::= BEGIN

	IMPORTS
		cAPSpecificBoundSet
	FROM CAP-classes classes
		CAMEL-AChBillingChargingCharacteristics {},
		CAMEL-CallResult {},
		CAMEL-FCIBillingChargingCharacteristics {},
		CAMEL-FCIGPRSBillingChargingCharacteristics {},
		CAMEL-FCISMSBillingChargingCharacteristics {},
		CAMEL-SCIBillingChargingCharacteristics,
		CAMEL-SCIBillingChargingCharacteristicsAlt,
		CAMEL-SCIGPRSBillingChargingCharacteristics
	FROM CAP-datatypes datatypes
		classes,
		datatypes
	FROM CAP-object-identifiers
			{itu-t(0) identified-organization(4) etsi(0) mobileDomain(0) umts-network(1) modules(3) cap-object-identifiers(100) version8(7)};

	PduAChBillingChargingCharacteristics ::= CAMEL-AChBillingChargingCharacteristics {cAPSpecificBoundSet}

	PduCallResult ::= CAMEL-CallResult {cAPSpecificBoundSet}

	PduFCIBillingChargingCharacteristics ::= CAMEL-FCIBillingChargingCharacteristics {cAPSpecificBoundSet}

	PduFCIGPRSBillingChargingCharacteristics ::= CAMEL-FCIGPRSBillingChargingCharacteristics {cAPSpecificBoundSet}

	PduFCISMSBillingChargingCharacteristics ::= CAMEL-FCISMSBillingChargingCharacteristics {cAPSpecificBoundSet}

	PduSCIBillingChargingCharacteristics ::= CAMEL-SCIBillingChargingCharacteristics

	PduSCIBillingChargingCharacteristicsAlt ::= CAMEL-SCIBillingChargingCharacteristicsAlt

	PduSCIGPRSBillingChargingCharacteristics ::= CAMEL-SCIGPRSBillingChargingCharacteristics

END
