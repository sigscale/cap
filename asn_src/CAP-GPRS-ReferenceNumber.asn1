CAP-GPRS-ReferenceNumber {itu-t(0) identified-organization(4) etsi(0) mobileDomain(0) umts-network(1) modules(3) cap-dialogueInformation(111) version8(7)}
-- Module CAP-GPRS-ReferenceNumber is updated to version8(7) for Rel-6. The definitions
-- in this module are not modified, compared to Rel-5.

DEFINITIONS ::= BEGIN

	EXPORTS
		id-CAP-GPRS-ReferenceNumber,
		cAP-GPRS-ReferenceNumber-Abstract-Syntax;

	IMPORTS

		Integer4
	FROM CS1-DataTypes {itu-t(0) identified-organization(4) etsi(0) inDomain(1) in-network(1)
	modules(0) cs1-datatypes(2) version1(0)}
	;

	id-CAP-GPRS-ReferenceNumber OBJECT IDENTIFIER ::= {itu-t(0) identified-organization(4) etsi(0) mobileDomain(0) umts-network(1) as(1) cap-GPRS-ReferenceNumber(5) version3(2)}

	cAP-GPRS-ReferenceNumber-Abstract-Syntax ABSTRACT-SYNTAX ::= {CAP-GPRS-ReferenceNumber IDENTIFIED BY id-CAP-GPRS-ReferenceNumber}

	CAP-GPRS-ReferenceNumber ::= SEQUENCE {
		destinationReference				[0] Integer4								OPTIONAL,
		originationReference				[1] Integer4								OPTIONAL
		}
	--  This parameter is used to identify the relationship between SGSN and the gsmSCF.

END
